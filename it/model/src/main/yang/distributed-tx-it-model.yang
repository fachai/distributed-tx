module distributed-tx-it-model{
        yang-version 1;
        namespace "urn:opendaylight:params:xml:ns:yang:distributed-tx:it:model";
        prefix "distributed-tx-it-model";

        revision "2015-01-05" {
                description "Initial revision of distributed-tx-it model";
        }

        typedef operation-type{
          type enumeration {
               enum "PUT" {
                    value 1;
                    description
                         "The put operation";
               }
               enum "MERGE" {
                     value 2;
                     description
                          "The merge operation";
               }
               enum "DELETE" {
                     value 3;
                     description
                           "The delete operation";
               }
           }
           description
              "The operation type of the transaction";
        }

        typedef status-type{
          type enumeration {
              enum "OK" {
                  value 1;
              }
              enum "FAILED" {
                  value 2;
              }
              enum "TEST-IN-PROGRESS" {
                  value 3;
              }
          }
          description
              "Indicates whether the test finished successfully";
        }

        typedef test-type{
          type enumeration {
              enum "NORMAL" {
                   value 1;
              }
              enum "ROLLBACK-ON-FAILURE"{
                   value 2;
              }
              enum "ROLLBACK" {
                   value 3;
              }
          }
          description
              "Stand for the test type, normal test is used for test DTx writing ability,
               rollback on failure test is used to test neither DTx action rollback or submit rollback,
               rollback test is used to test DTx rollback ability";
        }

        container datastore-test-data {
            config true;
            list outer-list {
                key id;
                leaf id {
                   type int32;
                }
                list inner-list {
                   key name;
                   leaf name {
                      type int32;
                   }
                   leaf value {
                      type string;
                   }
                }
            }
        }

        container test-status {
                leaf execStatus {
                    type enumeration {
                        enum "idle" {
                            value 1;
                        }
                        enum "executing" {
                            value 2;
                        }
                    }
                    config false;
                    mandatory true;
                    description
                        "Indicates whether a test run is in progress; only one test can run at a time";
                }
        }

	    rpc benchmark-test {
                  input {
                      leaf logicalTxType {
                         mandatory true;
                         type enumeration {
                            enum "DATASTORE" {
                                 value 1;
                                 description
                                    "operations on datastore nodes";
                            }
                            enum "NETCONF" {
                                 value 2;
                                 description
                                    "operations on netconf nodes";
                            }
                         }
                      }
                      leaf loop {
                          type int32;
                          default 1;
                          description
                             "The times of the test";
                      }
                      leaf operation {
                           type operation-type;
                      }
                      leaf putsPerTx {
                           type int32;
                           default 1;
                           description
                                "Number of write operations (PUT, MERGE, or DELETE) per transaction submit";
                      }
                      leaf outerList {
                           type int32;
                           default 1000;
                           description
                                "Size of outerList";
                      }
                      leaf innerList {
                           type int32;
                           default 1000;
                           description
                               "Size of innerList";
                      }
                  }
                  output {
                      leaf status {
                           mandatory true;
                           type status-type;
                           description
                               "Indicates whether the test finished successfully";
                      }
                      leaf execTime {
                           type uint32;
                           default 1;
                           description
                              "The time it took to execute all the transaction via databroker or netconf";
                      }
                      leaf dtxSyncExecTime {
                           type uint32;
                           default 1;
                           description
                              "The time it took to synchronously execute all the transaction via dtx";
                      }
                      leaf dtxAsyncExecTime {
                           type uint32;
                           default 1;
                           description
                              "The time it took to asynchronously execute all the transaction via dtx";
                      }
                      leaf dbOk {
                           type int32;
                           default 0;
                           description
                              "The number of successful databroker tests";
                      }
                      leaf dTxSyncOk {
                           type int32;
                           default 0;
                           description
                              "The number of successful dtx sync tests ";
                      }
                      leaf dTxAsyncOk {
                           type int32;
                           default 0;
                           description
                              "The number of successful dtx async tests ";
                      }
                  }
        }
        rpc datastore-test{
            input {
              leaf operation {
                  mandatory true;
                  type operation-type;
                  default "PUT";
                }
              leaf putsPerTx {
                 type int32;
                 default 1;
                 description
                     "number of operations {PUT,MERGE,DELETE} per submit";
              }
              leaf outerList {
                 type int32;
                 default 10;
                 description
                     "Size of outerList";
              }
              leaf innerList {
                 type int32;
                 default 10;
                 description
                     "Size of innerList";
              }
              leaf type {
                 type test-type;
                 default "NORMAL";
              }
            }
            output {
              leaf status {
                 type status-type;
              }
            }
            description
               "perform the dtx datastore test";
        }
        rpc netconf-test{
            input {
              leaf operation {
                 mandatory true;
                 type operation-type;
                 default "PUT";
              }
              leaf putsPerTx {
                 type int32;
                 default 1;
                 description
                    "number of operations {PUT,MERGE,DELETE} per submit";
              }
              leaf numberOfTxs {
                 type int32;
                 default 1;
                 description
                    "number of transations";
              }
              leaf type {
                 type test-type;
                 default "NORMAL";
              }
            }
            output {
               leaf status {
                 type status-type;
               }
            }
            description
                "perform dtx netconf test";
        }
        rpc mixed-provider-test{
            input {
               leaf operation {
                   mandatory true;
                   type operation-type;
                   default "PUT";
               }
               leaf putsPerTx {
                   type int32;
                   default 1;
                   description
                       "number of operations {PUT,MERGE,DELETE} per submit";
               }
               leaf numberOfTxs {
                    type int32;
                    default 10;
                    description
                         "number of netconf transactions";
               }
               leaf type {
                    type test-type;
                    default "NORMAL";
               }
            }
            output {
               leaf status {
                  type status-type;
               }
            }
            description
               "test mixed provider DTx";
        }
}
